module cloudshell {
    yang-version 1;
    namespace "urn:opendaylight:params:xml:ns:yang:cloudshell";
    prefix "cloudshell";

    revision "2015-01-05" {
        description "Initial revision of cloudshell model";
    }

    rpc create-route {
        input {
           leaf src_switch { type string; mandatory true; }
           leaf src_port { type uint16; mandatory true; }
           leaf dst_switch { type string; mandatory true; }
           leaf dst_port { type uint16; mandatory true; }
           leaf src_rules { type string; mandatory true; }
           leaf dst_rules { type string; mandatory true; }
           leaf allow { type boolean; default true; }
        }
        output {
            leaf success { type boolean; default false; }
        }
    }
}
